;;;Подготовка к использованию средств интерфейса объектно-ориентированного
;;;программирования ActiveX Automation
(defun begin_activex ( / )
  (vl-load-com)
  (setq acad_application (vlax-get-acad-object))
  (setq active_document (vla-get-ActiveDocument acad_application))
  (setq model_space (vla-get-ModelSpace active_document))
  (setq paper_space (vla-get-PaperSpace active_document))
 );defun begin_activex
